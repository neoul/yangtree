module openconfig-versioned-mod {
  namespace "urn:vm";
  prefix "oc-vm";

  import openconfig-ext { prefix "oc-ext"; }

  oc-ext:openconfig-version "12.4.2";
  organization "openconfig";

  container a { leaf b { type string; } }
}
