module openconfig-simple-deviation {
  prefix "oc-simple-deviation";
  namespace "urn:oc-simple-deviation";
  revision "2021-08-05";

  import openconfig-simple-target { prefix "t"; }

  deviation /t:native/t:state/t:b {
    description "Not supported";
    deviate not-supported;
  }
}
