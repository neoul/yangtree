module example-last-modified {
    revision "2021-11-02";
    namespace "http://example.org/example-last-modified";
    prefix "elm";
    import ietf-yang-types {
        prefix "yang";
    }
    import ietf-yang-metadata {
        prefix "md";
    }
    md:annotation last-modified {
        type yang:date-and-time;
        description
            "This annotation contains the date and time when the
            annotated instance was last modified (or created).";
    }
}
