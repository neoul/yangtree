module openconfig-simple-target {
  prefix "t";
  namespace "urn:t";
  revision "2021-08-05";

  container target {}

  container native {
    container config {
      leaf a { type string; }
    }
    container state {
      config false;
      leaf a { type string; }
      leaf b { type string; }
    }
  }
}
