module sample {
  prefix "simple";
  namespace "urn:network";
  // meta
  organization "sample model";

  contact "neoul@ymail.com";

  // Max line length throughout the modules should be 70 cols.

  // Formatting description statements: for consistency, the
  // description text should start on the line following the
  // 'description' keyword and be indented 2 spaces.
  description
    "example model description!";

  revision "2020-06-01" {
    description
      "Inital model";
    reference "0.1.1";
  }

  container sample {
    leaf bits-val {
      type bits {
        bit zero {
          position 0;
        }
        bit one {
          position 1;
        }
        bit two {
          position 2;
        }
      }
      default "auto-sense-speed";
    }
    anydata any {
     description "any data node can be placed this node"; 
    }
    leaf str-val { type string; }
    leaf empty-val { type empty; }
    list single-key-list {
      key "list-key";
      leaf list-key { type string; }
      leaf country-code { type string; }
      leaf uint32-range {
        config false;
        type uint32 { range "1..492"; }
      }
      leaf int8-range { type int8; }
      leaf decimal-range {
        type decimal64 {
          fraction-digits 2;
          range "1 .. 3.14 | 10 | 20..max";
        }
      }
      leaf empty-node {
        type empty;
      }
      leaf uint64-node {
        type uint64;
      }
    }
    list ordered-by-user-list {
      ordered-by user;
    }

    list non-key-list {
      leaf uintval { type uint32; }
      leaf strval { type string; }
    }

    list multiple-key-list {
      key "str integer";
      leaf integer { type uint32; }
      leaf str { type string; }
      leaf ok {type boolean;}
    }

    container container-val {
      leaf-list leaf-list-val {
        type string;
      }

      leaf test-instance-identifier {
        type instance-identifier;
        when "../enum-val='enum2'" {
          description
            "When statement test";
        }
      }

      leaf test-default {
        type int8;
        default 1;
      }

      leaf test-must {
        type int32;
        must "current() = count(../leaf-list-val)" {
          description
            "must statement test";
          error-message "test-must must be the number of ../leaf-list-val";
        }
      }

      choice test-choice {     // This example is illegal YANG
        case test-case-a {
            leaf a {
              type string; 
            }
        }
        case test-case-b {
            container b {
            }
        }
      }
      
      leaf enum-val {
        type enumeration {
          enum enum1;
          enum enum2;
          enum enum3 {
            value 30;
          }
        }
      }
    }
    leaf-list leaf-list-ro {
      config false;
      type string;
    }
    leaf-list leaf-list-rw {
      type string;
    }
  }
}
