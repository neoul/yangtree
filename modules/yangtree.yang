module yangtree {
  prefix "yangtree";
  namespace "https://github.com/neoul/yangtree";
  organization "yangtree";
  contact "neoul@ymail.com";
  description "This YANG module defines a fake schema node 
    to keep the schema tree of the loaded yangtree.";
  revision "2020-08-18" {
    description "Inital model";
  }

  anydata root {
    description "This node is used to the root schema node of the loaded yangtree";
  }

  anydata collector {
    description "This node is used to the collector schema node of the loaded yangtree";
  }
}
